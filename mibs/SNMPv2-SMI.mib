-- WinAgents MIB Extraction Wizard
-- Extracted from rfc2578.txt 16.03.2005 20:21:49

SNMPv2-SMI DEFINITIONS ::= BEGIN


-- the path to the root

org            OBJECT IDENTIFIER ::= { iso 3 }  --  "iso" = 1
dod            OBJECT IDENTIFIER ::= { org 6 }
internet       OBJECT IDENTIFIER ::= { dod 1 }

directory      OBJECT IDENTIFIER ::= { internet 1 }

mgmt           OBJECT IDENTIFIER ::= { internet 2 }
mib-2          OBJECT IDENTIFIER ::= { mgmt 1 }
transmission   OBJECT IDENTIFIER ::= { mib-2 10 }

experimental   OBJECT IDENTIFIER ::= { internet 3 }

private        OBJECT IDENTIFIER ::= { internet 4 }
enterprises    OBJECT IDENTIFIER ::= { private 1 }

security       OBJECT IDENTIFIER ::= { internet 5 }

snmpV2         OBJECT IDENTIFIER ::= { internet 6 }

-- transport domains
snmpDomains    OBJECT IDENTIFIER ::= { snmpV2 1 }

-- transport proxies
snmpProxys     OBJECT IDENTIFIER ::= { snmpV2 2 }

-- module identities
snmpModules    OBJECT IDENTIFIER ::= { snmpV2 3 }

-- Extended UTCTime, to allow dates with four-digit years
-- (Note that this definition of ExtUTCTime is not to be IMPORTed
--  by MIB modules.)
ExtUTCTime ::= OCTET STRING(SIZE(11 | 13))
    -- format is YYMMDDHHMMZ or YYYYMMDDHHMMZ
    --   where: YY   - last two digits of year (only years
    --                 between 1900-1999)
    --          YYYY - last four digits of the year (any year)
    --          MM   - month (01 through 12)
    --          DD   - day of month (01 through 31)
    --          HH   - hours (00 through 23)
    --          MM   - minutes (00 through 59)
    --          Z    - denotes GMT (the ASCII character Z)
    --
    -- For example, "9502192015Z" and "199502192015Z" represent
    -- 8:15pm GMT on 19 February 1995. Years after 1999 must use
    -- the four digit year format. Years 1900-1999 may use the
    -- two or four digit format.

-- definitions for information modules

-- MIB Extraction: All MACRO definitions are predefined by compiler
-- commented by MIB Extraction: MODULE-IDENTITY MACRO ::=
-- commented by MIB Extraction: BEGIN
-- commented by MIB Extraction:     TYPE NOTATION ::=
-- commented by MIB Extraction:                   "LAST-UPDATED" value(Update ExtUTCTime)
-- commented by MIB Extraction:                   "ORGANIZATION" Text
-- commented by MIB Extraction:                   "CONTACT-INFO" Text
-- commented by MIB Extraction:                   "DESCRIPTION" Text
-- commented by MIB Extraction:                   RevisionPart
-- commented by MIB Extraction: 
-- commented by MIB Extraction:     VALUE NOTATION ::=
-- commented by MIB Extraction:                   value(VALUE OBJECT IDENTIFIER)
-- commented by MIB Extraction: 
-- commented by MIB Extraction:     RevisionPart ::=
-- commented by MIB Extraction:                   Revisions
-- commented by MIB Extraction:                 | empty
-- commented by MIB Extraction:     Revisions ::=
-- commented by MIB Extraction:                   Revision
-- commented by MIB Extraction:                 | Revisions Revision
-- commented by MIB Extraction:     Revision ::=
-- commented by MIB Extraction:                   "REVISION" value(Update ExtUTCTime)
-- commented by MIB Extraction:                   "DESCRIPTION" Text
-- commented by MIB Extraction: 
-- commented by MIB Extraction:      a character string as defined in section 3.1.1
-- commented by MIB Extraction:     Text ::= value(IA5String)
-- commented by MIB Extraction: END


-- MIB Extraction: All MACRO definitions are predefined by compiler
-- commented by MIB Extraction: OBJECT-IDENTITY MACRO ::=
-- commented by MIB Extraction: BEGIN
-- commented by MIB Extraction:     TYPE NOTATION ::=
-- commented by MIB Extraction:                   "STATUS" Status
-- commented by MIB Extraction:                   "DESCRIPTION" Text
-- commented by MIB Extraction:                   ReferPart
-- commented by MIB Extraction: 
-- commented by MIB Extraction:     VALUE NOTATION ::=
-- commented by MIB Extraction:                   value(VALUE OBJECT IDENTIFIER)
-- commented by MIB Extraction: 
-- commented by MIB Extraction:     Status ::=
-- commented by MIB Extraction:                   "current"
-- commented by MIB Extraction:                 | "deprecated"
-- commented by MIB Extraction:                 | "obsolete"
-- commented by MIB Extraction: 
-- commented by MIB Extraction:     ReferPart ::=
-- commented by MIB Extraction:                   "REFERENCE" Text
-- commented by MIB Extraction:                 | empty
-- commented by MIB Extraction: 
-- commented by MIB Extraction:      a character string as defined in section 3.1.1
-- commented by MIB Extraction:     Text ::= value(IA5String)
-- commented by MIB Extraction: END


-- names of objects
-- (Note that these definitions of ObjectName and NotificationName
--  are not to be IMPORTed by MIB modules.)

ObjectName ::=
    OBJECT IDENTIFIER

NotificationName ::=
    OBJECT IDENTIFIER

-- syntax of objects

-- the "base types" defined here are:
--   3 built-in ASN.1 types: INTEGER, OCTET STRING, OBJECT IDENTIFIER
--   8 application-defined types: Integer32, IpAddress, Counter32,
--              Gauge32, Unsigned32, TimeTicks, Opaque, and Counter64

ObjectSyntax ::=
    CHOICE {
        simple
            SimpleSyntax,

          -- note that SEQUENCEs for conceptual tables and
          -- rows are not mentioned here...

        application-wide
            ApplicationSyntax
    }

-- built-in ASN.1 types

SimpleSyntax ::=
    CHOICE {
        -- INTEGERs with a more restrictive range
        -- may also be used
        integer-value               -- includes Integer32
            INTEGER (-2147483648..2147483647),

        -- OCTET STRINGs with a more restrictive size
        -- may also be used
        string-value
            OCTET STRING (SIZE (0..65535)),

        objectID-value
            OBJECT IDENTIFIER
    }

-- indistinguishable from INTEGER, but never needs more than
-- 32-bits for a two's complement representation
Integer32 ::=
        INTEGER (-2147483648..2147483647)


-- application-wide types

ApplicationSyntax ::=
    CHOICE {
        ipAddress-value
            IpAddress,

        counter-value
            Counter32,

        timeticks-value
            TimeTicks,

        arbitrary-value
            Opaque,

        big-counter-value
            Counter64,

        unsigned-integer-value  -- includes Gauge32
            Unsigned32
    }

-- in network-byte order
-- (this is a tagged type for historical reasons)
IpAddress ::=
    [APPLICATION 0]
        IMPLICIT OCTET STRING (SIZE (4))

-- this wraps
Counter32 ::=
    [APPLICATION 1]
        IMPLICIT INTEGER (0..4294967295)

-- this doesn't wrap
Gauge32 ::=
    [APPLICATION 2]
        IMPLICIT INTEGER (0..4294967295)

-- an unsigned 32-bit quantity
-- indistinguishable from Gauge32
Unsigned32 ::=
    [APPLICATION 2]
        IMPLICIT INTEGER (0..4294967295)

-- hundredths of seconds since an epoch
TimeTicks ::=
    [APPLICATION 3]
        IMPLICIT INTEGER (0..4294967295)

-- for backward-compatibility only
Opaque ::=
    [APPLICATION 4]
        IMPLICIT OCTET STRING

-- for counters that wrap in less than one hour with only 32 bits
Counter64 ::=
    [APPLICATION 6]
        IMPLICIT INTEGER (0..18446744073709551615)


-- definition for objects

-- MIB Extraction: All MACRO definitions are predefined by compiler
-- commented by MIB Extraction: OBJECT-TYPE MACRO ::=
-- commented by MIB Extraction: BEGIN
-- commented by MIB Extraction:     TYPE NOTATION ::=
-- commented by MIB Extraction:                   "SYNTAX" Syntax
-- commented by MIB Extraction:                   UnitsPart
-- commented by MIB Extraction:                   "MAX-ACCESS" Access
-- commented by MIB Extraction:                   "STATUS" Status
-- commented by MIB Extraction:                   "DESCRIPTION" Text
-- commented by MIB Extraction:                   ReferPart
-- commented by MIB Extraction:                   IndexPart
-- commented by MIB Extraction:                   DefValPart
-- commented by MIB Extraction: 
-- commented by MIB Extraction:     VALUE NOTATION ::=
-- commented by MIB Extraction:                   value(VALUE ObjectName)
-- commented by MIB Extraction: 
-- commented by MIB Extraction:     Syntax ::=    Must be one of the following:
-- commented by MIB Extraction:                         a base type (or its refinement),
-- commented by MIB Extraction:                         a textual convention (or its refinement), or
-- commented by MIB Extraction:                         a BITS pseudo-type
-- commented by MIB Extraction:                    type
-- commented by MIB Extraction:                 | "BITS" "{" NamedBits "}"
-- commented by MIB Extraction: 
-- commented by MIB Extraction:     NamedBits ::= NamedBit
-- commented by MIB Extraction:                 | NamedBits "," NamedBit
-- commented by MIB Extraction: 
-- commented by MIB Extraction:     NamedBit ::=  identifier "(" number ")"  number is nonnegative
-- commented by MIB Extraction: 
-- commented by MIB Extraction:     UnitsPart ::=
-- commented by MIB Extraction:                   "UNITS" Text
-- commented by MIB Extraction:                 | empty
-- commented by MIB Extraction: 
-- commented by MIB Extraction:     Access ::=
-- commented by MIB Extraction:                   "not-accessible"
-- commented by MIB Extraction:                 | "accessible-for-notify"
-- commented by MIB Extraction:                 | "read-only"
-- commented by MIB Extraction:                 | "read-write"
-- commented by MIB Extraction:                 | "read-create"
-- commented by MIB Extraction: 
-- commented by MIB Extraction:     Status ::=
-- commented by MIB Extraction:                   "current"
-- commented by MIB Extraction:                 | "deprecated"
-- commented by MIB Extraction:                 | "obsolete"
-- commented by MIB Extraction: 
-- commented by MIB Extraction:     ReferPart ::=
-- commented by MIB Extraction:                   "REFERENCE" Text
-- commented by MIB Extraction:                 | empty
-- commented by MIB Extraction: 
-- commented by MIB Extraction:     IndexPart ::=
-- commented by MIB Extraction:                   "INDEX"    "{" IndexTypes "}"
-- commented by MIB Extraction:                 | "AUGMENTS" "{" Entry      "}"
-- commented by MIB Extraction:                 | empty
-- commented by MIB Extraction:     IndexTypes ::=
-- commented by MIB Extraction:                   IndexType
-- commented by MIB Extraction:                 | IndexTypes "," IndexType
-- commented by MIB Extraction:     IndexType ::=
-- commented by MIB Extraction:                   "IMPLIED" Index
-- commented by MIB Extraction:                 | Index
-- commented by MIB Extraction:     Index ::=
-- commented by MIB Extraction:                      use the SYNTAX value of the
-- commented by MIB Extraction:                      correspondent OBJECT-TYPE invocation
-- commented by MIB Extraction:                   value(ObjectName)
-- commented by MIB Extraction:     Entry ::=
-- commented by MIB Extraction:                      use the INDEX value of the
-- commented by MIB Extraction:                      correspondent OBJECT-TYPE invocation
-- commented by MIB Extraction:                   value(ObjectName)
-- commented by MIB Extraction: 
-- commented by MIB Extraction:     DefValPart ::= "DEFVAL" "{" Defvalue "}"
-- commented by MIB Extraction:                 | empty
-- commented by MIB Extraction: 
-- commented by MIB Extraction:     Defvalue ::=   must be valid for the type specified in
-- commented by MIB Extraction:                    SYNTAX clause of same OBJECT-TYPE macro
-- commented by MIB Extraction:                   value(ObjectSyntax)
-- commented by MIB Extraction:                 | "{" BitsValue "}"
-- commented by MIB Extraction: 
-- commented by MIB Extraction:     BitsValue ::= BitNames
-- commented by MIB Extraction:                 | empty
-- commented by MIB Extraction: 
-- commented by MIB Extraction:     BitNames ::=  BitName
-- commented by MIB Extraction:                 | BitNames "," BitName
-- commented by MIB Extraction: 
-- commented by MIB Extraction:     BitName ::= identifier
-- commented by MIB Extraction: 
-- commented by MIB Extraction:      a character string as defined in section 3.1.1
-- commented by MIB Extraction:     Text ::= value(IA5String)
-- commented by MIB Extraction: END


-- definitions for notifications

-- MIB Extraction: All MACRO definitions are predefined by compiler
-- commented by MIB Extraction: NOTIFICATION-TYPE MACRO ::=
-- commented by MIB Extraction: BEGIN
-- commented by MIB Extraction:     TYPE NOTATION ::=
-- commented by MIB Extraction:                   ObjectsPart
-- commented by MIB Extraction:                   "STATUS" Status
-- commented by MIB Extraction:                   "DESCRIPTION" Text
-- commented by MIB Extraction:                   ReferPart
-- commented by MIB Extraction: 
-- commented by MIB Extraction:     VALUE NOTATION ::=
-- commented by MIB Extraction:                   value(VALUE NotificationName)
-- commented by MIB Extraction: 
-- commented by MIB Extraction:     ObjectsPart ::=
-- commented by MIB Extraction:                   "OBJECTS" "{" Objects "}"
-- commented by MIB Extraction:                 | empty
-- commented by MIB Extraction:     Objects ::=
-- commented by MIB Extraction:                   Object
-- commented by MIB Extraction:                 | Objects "," Object
-- commented by MIB Extraction:     Object ::=
-- commented by MIB Extraction:                   value(ObjectName)
-- commented by MIB Extraction: 
-- commented by MIB Extraction:     Status ::=
-- commented by MIB Extraction:                   "current"
-- commented by MIB Extraction:                 | "deprecated"
-- commented by MIB Extraction:                 | "obsolete"
-- commented by MIB Extraction: 
-- commented by MIB Extraction:     ReferPart ::=
-- commented by MIB Extraction:                   "REFERENCE" Text
-- commented by MIB Extraction:                 | empty
-- commented by MIB Extraction: 
-- commented by MIB Extraction:      a character string as defined in section 3.1.1
-- commented by MIB Extraction:     Text ::= value(IA5String)
-- commented by MIB Extraction: END

-- definitions of administrative identifiers

zeroDotZero    OBJECT-IDENTITY
    STATUS     current
    DESCRIPTION
            "A value used for null identifiers."
    ::= { 0 0 }

END
